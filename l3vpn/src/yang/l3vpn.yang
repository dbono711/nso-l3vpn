module l3vpn {
  yang-version 1.1;
  namespace "http://dbono711/l3vpn";
  prefix l3vpn;

  import ietf-inet-types { prefix inet; }
  import ietf-routing-types { prefix rt-types; }
  import tailf-common { prefix tailf; }
  import tailf-ncs { prefix ncs; }

  organization
    "Darren Bono";

  contact
    "darren.bono@att.net";

  description
    "NSO service package for basic MPLS Layer 3 VPN (L3VPN) services";

  revision 2024-12-13 {
    description "Add support for IOS devices";
  }

  revision 2021-10-18 {
    description "Initial revision";
  }

  grouping interface {
    leaf cir {
      tailf:info "Committed Information Rate (Mbps) for interface policy";
      type uint32;
      default 1;
    }

    leaf mtu {
      tailf:info "Maximum Transmission Unit (MTU)";
      type uint32 {
        range 1500..9000;
      }
      default 2000;
    }

    leaf port-mode {
      tailf:info "Apply service on port level";
      type boolean;
      mandatory true;
    }

    leaf efp-id {
      tailf:display-when "false()";
      tailf:info "Ethernet Flow Point ID";
      type uint16;
    }

    leaf-list vlan-id {
      tailf:info "Service encapsulation VLAN ID";
      when "../port-mode = 'false'";
      min-elements 1;
      type uint16 {
        range "1 .. 4094";
      }
    }

    leaf-list inner-vlan-id {
      tailf:info "Service encapsulation inner VLAN ID";
      when "../vlan-id";
      type uint16 {
        range "1 .. 4094";
      }
    }

    leaf ipv4-local-prefix {
      tailf:info "IPv4 address of the local interface";
      when "../../../../inet = 'IPv4' or ../../../../inet = 'IPv4-IPv6'";
      type tailf:ipv4-address-and-prefix-length;
    }

    leaf ipv6-local-prefix {
      tailf:info "IPv6 address of the local interface";
      when "../../../../inet = 'IPv6' or ../../../../inet = 'IPv4-IPv6'";
      type tailf:ipv6-address-and-prefix-length;
    }
  }

  grouping bgp-neighbor {
    leaf password {
      tailf:info "BGP neighbor password";
      tailf:suppress-echo true;
      type tailf:aes-cfb-128-encrypted-string {
        tailf:info "Password, minimum of 8 characters";
      }
    }
  }

  augment /ncs:services {
    list l3vpn {
      tailf:info "MPLS Layer 3 Virtual Private Network (L3VPN) Services";
      description "mpls l3vpn service package";
      key "customer-name service-id";

      uses ncs:service-data;
      ncs:servicepoint l3vpn-servicepoint;

      leaf customer-name {
        tailf:info "Customer name";
        type leafref {
          path "/ncs:customers/ncs:customer/ncs:id";
        }
      }

      leaf service-id {
        tailf:info "Service identifier";
        tailf:cli-allow-range;
        type string;
      }

      leaf vpn-id {
        tailf:info "VPN identifier - used to derive RT and RD values.";
        type uint16;
      }

      leaf inet {
        tailf:info "Address family supported by the MPLS VPN";
        type enumeration {
          enum IPv4;
          enum IPv6;
          enum IPv4-IPv6;
        }
        default "IPv4";
      }

      leaf max-routes {
        tailf:info "The maximum number of routes the MPLS VPN should accept";
        type uint16 {
          tailf:info "< 1 - 5000 >";
          range "1..5000";
        }
        default 100;
      }

      leaf max-routes-warning {
        tailf:info "The threshold (%) for producing a warning for 'max-routes'";
        type uint8 {
          tailf:info "< 1 - 100 >";
          range "1..100";
        }
        default 80;
      }

      container provider-edge {
        tailf:info "Provider Edge (PE) configuration";

        leaf asn {
          tailf:info "Autonomous System Number (ASN) for the MPLS Provider domain";
          mandatory true;
          type inet:as-number;
        }

        list device {
          tailf:info "Provider Edge device";
          min-elements 2;
          key name;

          leaf name {
            type leafref {
              path "/ncs:devices/ncs:device/ncs:name";
            }
            must "contains(/ncs:devices/ncs:device[ncs:name=current()/../name]/ncs:device-type/ncs:cli/ncs:ned-id, 'cisco-ios-cli') or
              contains(/ncs:devices/ncs:device[ncs:name=current()/../name]/ncs:device-type/ncs:cli/ncs:ned-id, 'cisco-iosxr-cli')" {
              error-message "Provider Edge devices must be Cisco IOS or Cisco IOS-XR";
            }
          }

          leaf-list redistribute {
            tailf:info "Redistribution protocols";
            type enumeration {
              enum static;
              enum connected;
            }
          }

          list interface {
            tailf:info "PE interface";
            min-elements 1;
            key name;

            leaf name {
              tailf:cli-completion-actionpoint l3vpn-interface-name {
                tailf:cli-completion-id "provideredge-";
              }
              type string;
            }

            uses interface;
          }

          container ce-routing {
            tailf:info "Customer Edge Routing";
            presence "true";

            container static {
              tailf:info "Static Routes";
              presence "true";

              list ipv4-destination-prefix {
                tailf:info "Destination Prefix";
                when "(../../../../../inet = 'IPv4' or ../../../../../inet = 'IPv4-IPv6')";
                key ipv4-prefix;

                leaf ipv4-prefix {
                  tailf:info "Destination for static route";
                  type inet:ipv4-prefix;
                }

                leaf-list ipv4-forwarding {
                  tailf:info "Static route next-hop";
                  min-elements 1;
                  type inet:ipv4-address;
                }
              }

              list ipv6-destination-prefix {
                tailf:info "Destination Prefix";
                when "(../../../../../inet = 'IPv6' or ../../../../../inet = 'IPv4-IPv6')";
                key ipv6-prefix;

                leaf ipv6-prefix {
                  tailf:info "Destination for static route";
                  type inet:ipv6-prefix;
                }

                leaf-list ipv6-forwarding {
                  tailf:info "Static route next-hop";
                  min-elements 1;
                  type inet:ipv6-address;
                }
              }
            }

            container bgp {
              tailf:info "Border Gateway Protocol";
              presence true;

              leaf asn {
                tailf:info "Customer Edge Autonomous System Number (ASN)";
                mandatory true;
                type inet:as-number;
              }

              leaf route-policy-in {
                tailf:info "Inbound BGP Route Policy";
                type string;
                default "PASS";
              }

              leaf route-policy-out {
                tailf:info "Outbound BGP Route Policy";
                type string;
                default "PASS";
              }

              list ipv4-neighbor {
                tailf:info "IPv4 BGP neighbor";
                when "(../../../../../inet = 'IPv4' or ../../../../../inet = 'IPv4-IPv6')";
                key address;

                leaf address {
                  tailf:info "IPv4 address of the BGP neighbor";
                  type inet:ipv4-address;
                }

                uses bgp-neighbor;
              }

              list ipv6-neighbor {
                tailf:info "IPv6 BGP neighbor";
                when "(../../../../../inet = 'IPv4' or ../../../../../inet = 'IPv4-IPv6')";
                key address;

                leaf address {
                  tailf:info "IPv6 address of the BGP neighbor";
                  type inet:ipv6-address;
                }

                uses bgp-neighbor;
              }
            }
          }
        }
      }
    }
  }
}
